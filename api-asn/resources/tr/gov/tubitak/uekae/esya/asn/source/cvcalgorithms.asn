cvcalgorithms
DEFINITIONS IMPLICIT TAGS ::= BEGIN

-- Object Identifiers related to a public key in a certificate
--sigs-iso9796-2withsha1	OBJECT IDENTIFIER ::= {1 3 36 3 4 2 2 1 }
sigs-iso9796-2withsha1	OCTET STRING ::= '2B240304020201'H
--sigs-iso9796-2withsha224	OBJECT IDENTIFIER ::= {1 3 36 3 4 2 2 3 }
sigs-iso9796-2withsha224	OCTET STRING ::= '2B240304020203'H
--sigs-iso9796-2withsha256	OBJECT IDENTIFIER ::= {1 3 36 3 4 2 2 4 }
sigs-iso9796-2withsha256	OCTET STRING ::= '2B240304020204'H
--sigs-iso9796-2withsha384	OBJECT IDENTIFIER ::= {1 3 36 3 4 2 2 5 }
sigs-iso9796-2withsha384	OCTET STRING ::= '2B240304020205'H
--sigs-iso9796-2withsha512	OBJECT IDENTIFIER ::= {1 3 36 3 4 2 2 6 }
sigs-iso9796-2withsha512	OCTET STRING ::= '2B240304020206'H

--enc-iso9796-2withrsasha1	OBJECT IDENTIFIER ::= {1 3 36 7 2 1 1}
enc-iso9796-2withrsasha1	OCTET STRING ::= '2B2407020101'H
--enc-iso9796-2withrsasha224	OBJECT IDENTIFIER ::= {1 3 36 7 2 1 3}
enc-iso9796-2withrsasha224	OCTET STRING ::= '2B2407020103'H
--enc-iso9796-2withrsasha256	OBJECT IDENTIFIER ::= {1 3 36 7 2 1 4}
enc-iso9796-2withrsasha256	OCTET STRING ::= '2B2407020104'H
--enc-iso9796-2withrsasha384	OBJECT IDENTIFIER ::= {1 3 36 7 2 1 5}
enc-iso9796-2withrsasha384	OCTET STRING ::= '2B2407020105'H
--enc-iso9796-2withrsasha512	OBJECT IDENTIFIER ::= {1 3 36 7 2 1 6}
enc-iso9796-2withrsasha512	OCTET STRING ::= '2B2407020106'H

--oid-dev_auth-privacy-SHA-1	OBJECT IDENTIFIER ::= {1 3 162 14890 2 4 1 1}
oid-dev_auth-privacy-SHA-1	OCTET STRING ::= '2B8122F42A02040101'H
--oid-dev_auth-privacy-SHA-224	OBJECT IDENTIFIER ::= {1 3 162 14890 2 4 1 3}
oid-dev_auth-privacy-SHA-224	OCTET STRING ::= '2B8122F42A02040103'H
--oid-dev_auth-privacy-SHA-256	OBJECT IDENTIFIER ::= {1 3 162 14890 2 4 1 4}
oid-dev_auth-privacy-SHA-256	OCTET STRING ::= '2B8122F42A02040104'H
--oid-dev_auth-privacy-SHA-384	OBJECT IDENTIFIER ::= {1 3 162 14890 2 4 1 5}
oid-dev_auth-privacy-SHA-384	OCTET STRING ::= '2B8122F42A02040105'H
--oid-dev_auth-privacy-SHA-512	OBJECT IDENTIFIER ::= {1 3 162 14890 2 4 1 6}
oid-dev_auth-privacy-SHA-512	OCTET STRING ::= '2B8122F42A02040106'H

--oid-dsi-ecdsa-SHA-1	OBJECT IDENTIFIER ::= {1 3 162 14890 2 3 1 1 1}
oid-dsi-ecdsa-SHA-1	OCTET STRING ::= '2B8122F42A0203010101'H
--oid-dsi-ecdsa-SHA-224	OBJECT IDENTIFIER ::= {1 3 162 14890 2 3 1 1 3}
oid-dsi-ecdsa-SHA-224	OCTET STRING ::= '2B8122F42A0203010103'H
--oid-dsi-ecdsa-SHA-256	OBJECT IDENTIFIER ::= {1 3 162 14890 2 3 1 1 4}
oid-dsi-ecdsa-SHA-256	OCTET STRING ::= '2B8122F42A0203010104'H

--oid-TA-ECDSA-SHA-1	OBJECT IDENTIFIER ::= {0 4 0 127 0 7 2 2 2 2 1}
oid-TA-ECDSA-SHA-1	OCTET STRING ::= '04007F00070202020201'H
--oid-TA-ECDSA-SHA-224	OBJECT IDENTIFIER ::= {0 4 0 127 0 7 2 2 2 2 2}
oid-TA-ECDSA-SHA-224	OCTET STRING ::= '04007F00070202020202'H
--oid-TA-ECDSA-SHA-256	OBJECT IDENTIFIER ::= {0 4 0 127 0 7 2 2 2 2 3}
oid-TA-ECDSA-SHA-256	OCTET STRING ::= '04007F00070202020203'H

--meac	OBJECT IDENTIFIER ::= {1 3 162 14890 2 4 2}
meac	OCTET STRING ::= '2B8122F42A020402'H



END
