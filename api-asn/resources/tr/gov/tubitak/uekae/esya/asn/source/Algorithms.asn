algorithms { iso(1) identified-organization(3) dod(6)
   internet(1) security(5) mechanisms(5) pkix(7) id-mod(0)
   id-mod-pkix1-algorithms(17) }

   DEFINITIONS EXPLICIT TAGS ::= BEGIN

   -- EXPORTS All;

   -- IMPORTS NONE;

   --
   --   DSA Keys and Signatures
   --

   -- OID for DSA public key

   id-dsa OBJECT IDENTIFIER ::= {
        iso(1) member-body(2) us(840) x9-57(10040) x9algorithm(4) 1 }
        
   -- encoding for DSA public key

   Dss-Parms  ::=  SEQUENCE  {
        p             INTEGER,
        q             INTEGER,
        g             INTEGER  }

   -- OID for DSA signature generated with SHA-1 hash

   id-dsa-with-sha1 OBJECT IDENTIFIER ::=  {
        iso(1) member-body(2) us(840) x9-57 (10040) x9algorithm(4) 3 }

   -- encoding for DSA signature generated with SHA-1 hash

   Dss-Sig-Value  ::=  SEQUENCE  {
        r       INTEGER,
        s       INTEGER  }
   --
   --   RSA Keys and Signatures
   --
   --

   -- arc for RSA public key and RSA signature OIDs
pkcs-1 OBJECT IDENTIFIER ::= {
        iso(1) member-body(2) us(840) rsadsi(113549) pkcs(1) 1 }

   -- OID for RSA public keys

   rsaEncryption OBJECT IDENTIFIER ::=  { pkcs-1 1 }

   -- OID for RSA signature generated with MD2 hash

   md2WithRSAEncryption OBJECT IDENTIFIER  ::=  { pkcs-1 2 }

   -- OID for RSA signature generated with MD5 hash

   md5WithRSAEncryption OBJECT IDENTIFIER  ::=  { pkcs-1 4 }

   -- OID for RSA signature generated with SHA-1 hash

   sha1WithRSAEncryption OBJECT IDENTIFIER  ::=  { pkcs-1 5 }

   -- OID for Password Based Encryption with sha and 40bit RC2_CBC
   pbe_with_Sha_and_40Bit_RC2_CBC  OBJECT IDENTIFIER ::= {1 2 840 113549 1 12 1 6 }
   -- OID for DES_EDE3_CBC 
   des_EDE3_CBC OBJECT IDENTIFIER ::= {iso(1) member-body(2) us(840) rsadsi(113549) 3 7 }
   -- OID for DES_EDE3_ECB
   des_EDE3_ECB OBJECT IDENTIFIER ::= {1 3 14 3 2 17 }

   id-alg-CMS3DESwrap OBJECT IDENTIFIER ::=
   {iso(1) member-body(2) us(840) rsadsi(113549) pkcs(1) pkcs-9(9) smime(16)
    alg(3) 6}

   id-alg-CMSRC2wrap OBJECT IDENTIFIER ::=
   {iso(1) member-body(2) us(840) rsadsi(113549) pkcs(1) pkcs-9(9) smime(16)
    alg(3) 7}
	
	hMAC-SHA1 OBJECT IDENTIFIER ::=
   {iso(1) identified-organization(3) dod(6) internet(1) security(5)
   mechanisms(5) 8 1 2}

   --
   --   Diffie-Hellman Keys
   --
   --

   -- OID for Password Based Encryption with ARC4_Sim_Stream_Cypher
   arc4_Sim_Stream_Cypher OBJECT IDENTIFIER ::= {1 0 9979 7 }

   dhpublicnumber OBJECT IDENTIFIER ::= {
      iso(1) member-body(2) us(840) ansi-x942(10046) number-type(2) 1 }

   DiffieHellmanPublicNumber ::= INTEGER
	  
   DomainParameters ::= SEQUENCE {
        p       INTEGER, -- odd prime, p=jq +1
        g       INTEGER, -- generator, g
        q       INTEGER, -- factor of p-1
        j       INTEGER OPTIONAL, -- subgroup factor, j>= 2
        validationParms  ValidationParms OPTIONAL }

   ValidationParms ::= SEQUENCE {
        seed             BIT STRING,
        pgenCounter      INTEGER }

   --
   --   KEA Keys
   --
   --

      id-keyExchangeAlgorithm  OBJECT IDENTIFIER   ::=
             { 2 16 840 1 101 2 1 1 22 }

      KEA-Parms-Id     ::= OCTET STRING

--
   --   Elliptic Curve Keys, Signatures, and Curves
   --
   --

   ansi-X9-62 OBJECT IDENTIFIER ::= {
      iso(1) member-body(2) us(840) 10045 }

   FieldID ::= SEQUENCE {            -- Finite field
      fieldType   OBJECT IDENTIFIER,
      parameters  ANY DEFINED BY fieldType
   }

   --
   --              ECDSA signatures
   --
   --

   -- Arc for ECDSA signature OIDS

   id-ecSigType OBJECT IDENTIFIER ::= { ansi-X9-62 signatures(4) }

   -- OID for ECDSA signatures with SHA-1

   ecdsa-with-SHA1 OBJECT IDENTIFIER ::= { id-ecSigType 1 }

   -- OID for an elliptic curve signature
   -- format for the value of an ECDSA signature value

   ECDSA-Sig-Value ::= SEQUENCE {
      r     INTEGER,
      s     INTEGER
   }

   --
   --                   Elliptic Curve Keys
   --
   --

   -- recognized field type OIDs are defined in the following arc

   id-fieldType OBJECT IDENTIFIER ::= { ansi-X9-62 fieldType(1) }

   -- where fieldType is prime-field, the parameters are of type Prime-p

   prime-field OBJECT IDENTIFIER ::= { id-fieldType 1 }

   Prime-p ::= INTEGER    -- Finite field F(p), where p is an odd prime
-- where fieldType is characteristic-two-field, the parameters are
   -- of type Characteristic-two

   characteristic-two-field OBJECT IDENTIFIER ::= { id-fieldType 2 }

   Characteristic-two ::= SEQUENCE {
      m           INTEGER,                      -- Field size 2^m
      basis       OBJECT IDENTIFIER,
      parameters  ANY DEFINED BY basis
   }

   -- recognized basis type OIDs are defined in the following arc

   id-characteristic-two-basis OBJECT IDENTIFIER ::= {
      characteristic-two-field basisType(3) }

   -- gnbasis is identified by OID gnBasis and indicates
   -- parameters are NULL

   gnBasis OBJECT IDENTIFIER ::= { id-characteristic-two-basis 1 }

   -- parameters for this basis are NULL

   -- trinomial basis is identified by OID tpBasis and indicates
   -- parameters of type Pentanomial

   tpBasis OBJECT IDENTIFIER ::= { id-characteristic-two-basis 2 }

   -- Trinomial basis representation of F2^m
   -- Integer k for reduction polynomial xm + xk + 1
   --

   Trinomial ::= INTEGER

   -- for pentanomial basis is identified by OID ppBasis and indicates
   -- parameters of type Pentanomial

   ppBasis OBJECT IDENTIFIER ::= { id-characteristic-two-basis 3 }

   Pentanomial ::= SEQUENCE {
      --
      -- Pentanomial basis representation of F2^m
      -- reduction polynomial integers k1, k2, k3
      -- f(x) = x**m + x**k3 + x**k2 + x**k1 + 1
      --
      k1  INTEGER,
      k2  INTEGER,
      k3  INTEGER
 }

   -- The object identifiers gnBasis, tpBasis and ppBasis name
   -- three kinds of basis for characteristic-two finite fields

   FieldElement ::= OCTET STRING                -- Finite field element

   ECPoint  ::= OCTET STRING                    -- Elliptic curve point

   -- Elliptic Curve parameters may be specfied explicitly,
   -- specified implicitly through a "named curve", or
   -- inherited from the CA

   EcpkParameters ::= CHOICE {
     ecParameters  ECParameters,
     namedCurve    OBJECT IDENTIFIER,
     implicitlyCA  NULL
   }

   ECParameters  ::= SEQUENCE {            -- Elliptic curve parameters
      version   ECPVer,
      fieldID   FieldID,
      curve     Curve,
      base      ECPoint,                   -- Base point G
      order     INTEGER,                   -- Order n of the base point
      cofactor  INTEGER  OPTIONAL          -- The integer h = #E(Fq)/n
   }

   ECPVer ::= INTEGER {ecpVer1(1)}

   Curve  ::= SEQUENCE {
      a     FieldElement,               -- Elliptic curve coefficient a
      b     FieldElement,               -- Elliptic curve coefficient b
      seed  BIT STRING  OPTIONAL
   }
   id-publicKeyType OBJECT IDENTIFIER  ::= { ansi-X9-62 keyType(2) }

   id-ecPublicKey OBJECT IDENTIFIER ::= { id-publicKeyType 1 }

   --     Named Elliptic Curves
   --
   -- Standards bodies may define OIDs to represent common
   -- elliptic curve parameters.  Users are encouraged
   -- to consult relevant standards and specifications to
   -- determine which OIDs (if any) are appropriate for their
   -- applications.

   -- The following OIDS are defined in ANSI X9.62.
ellipticCurve OBJECT IDENTIFIER ::= { ansi-X9-62 curves(3) }

   c-TwoCurve OBJECT IDENTIFIER ::= {
      ellipticCurve characteristicTwo(0) }

   primeCurve OBJECT IDENTIFIER ::= { ellipticCurve prime(1) }

   c2pnb163v1  OBJECT IDENTIFIER  ::=  { c-TwoCurve  1 }
   c2pnb163v2  OBJECT IDENTIFIER  ::=  { c-TwoCurve  2 }
   c2pnb163v3  OBJECT IDENTIFIER  ::=  { c-TwoCurve  3 }
   c2pnb176w1  OBJECT IDENTIFIER  ::=  { c-TwoCurve  4 }
   c2tnb191v1  OBJECT IDENTIFIER  ::=  { c-TwoCurve  5 }
   c2tnb191v2  OBJECT IDENTIFIER  ::=  { c-TwoCurve  6 }
   c2tnb191v3  OBJECT IDENTIFIER  ::=  { c-TwoCurve  7 }
   c2onb191v4  OBJECT IDENTIFIER  ::=  { c-TwoCurve  8 }
   c2onb191v5  OBJECT IDENTIFIER  ::=  { c-TwoCurve  9 }
   c2pnb208w1  OBJECT IDENTIFIER  ::=  { c-TwoCurve 10 }
   c2tnb239v1  OBJECT IDENTIFIER  ::=  { c-TwoCurve 11 }
   c2tnb239v2  OBJECT IDENTIFIER  ::=  { c-TwoCurve 12 }
   c2tnb239v3  OBJECT IDENTIFIER  ::=  { c-TwoCurve 13 }
   c2onb239v4  OBJECT IDENTIFIER  ::=  { c-TwoCurve 14 }
   c2onb239v5  OBJECT IDENTIFIER  ::=  { c-TwoCurve 15 }
   c2pnb272w1  OBJECT IDENTIFIER  ::=  { c-TwoCurve 16 }
   c2pnb304w1  OBJECT IDENTIFIER  ::=  { c-TwoCurve 17 }
   c2tnb359v1  OBJECT IDENTIFIER  ::=  { c-TwoCurve 18 }
   c2pnb368w1  OBJECT IDENTIFIER  ::=  { c-TwoCurve 19 }
   c2tnb431r1  OBJECT IDENTIFIER  ::=  { c-TwoCurve 20 }

   prime192v1  OBJECT IDENTIFIER  ::=  { primeCurve  1 }
   prime192v2  OBJECT IDENTIFIER  ::=  { primeCurve  2 }
   prime192v3  OBJECT IDENTIFIER  ::=  { primeCurve  3 }
   prime239v1  OBJECT IDENTIFIER  ::=  { primeCurve  4 }
   prime239v2  OBJECT IDENTIFIER  ::=  { primeCurve  5 }
   prime239v3  OBJECT IDENTIFIER  ::=  { primeCurve  6 }
   prime256v1  OBJECT IDENTIFIER  ::=  { primeCurve  7 }

sha-1 OBJECT IDENTIFIER ::= { iso(1) identified-organization(3) oiw(14) secsig(3) algorithm(2) 26}


md5 OBJECT IDENTIFIER ::= { iso(1) member-body(2)  us(840) rsadsi(113549) digestAlgorithm(2) 5}

ripemd-160 OBJECT IDENTIFIER ::= { iso(1) identified-organization(3) teletrust(36) algorithm(3) hashAlgorithm(2) ripemd160(1) }



-- RFC 4055'den alinanlar
id-sha224  OBJECT IDENTIFIER  ::=  { joint-iso-itu-t(2) country(16) us(840) organization(1) gov(101)
                           csor(3) nistalgorithm(4) hashalgs(2) 4 }
id-sha256  OBJECT IDENTIFIER  ::=  { joint-iso-itu-t(2) country(16) us(840) organization(1) gov(101)
                           csor(3) nistalgorithm(4) hashalgs(2) 1 }
id-sha384  OBJECT IDENTIFIER  ::=  { joint-iso-itu-t(2) country(16) us(840) organization(1) gov(101)
                           csor(3) nistalgorithm(4) hashalgs(2) 2 }
id-sha512  OBJECT IDENTIFIER  ::=  { joint-iso-itu-t(2) country(16) us(840) organization(1) gov(101)
                           csor(3) nistalgorithm(4) hashalgs(2) 3 }
                           
-- When the following OIDs are used in an AlgorithmIdentifier, the
-- parameters MUST be present and MUST be NULL.

sha224WithRSAEncryption  OBJECT IDENTIFIER  ::=  { pkcs-1 14 }
sha256WithRSAEncryption  OBJECT IDENTIFIER  ::=  { pkcs-1 11 }
sha384WithRSAEncryption  OBJECT IDENTIFIER  ::=  { pkcs-1 12 }
sha512WithRSAEncryption  OBJECT IDENTIFIER  ::=  { pkcs-1 13 }

-- When id-RSASSA-PSS is used in an AlgorithmIdentifier, and the
-- parameters field is present, it MUST be RSASSA-PSS-params.
id-RSASSA-PSS  OBJECT IDENTIFIER  ::=  { pkcs-1 10 }

-- When id-mgf1 is used in an AlgorithmIdentifier the parameters
-- MUST be present and MUST be a HashAlgorithm.
id-mgf1  OBJECT IDENTIFIER  ::=  { pkcs-1 8 }

id-RSASS-ISO9796d2 OBJECT IDENTIFIER ::= { iso(1) standard(0) signature-schemes(9796) part2(2) mechanismHash(2) normal(1) mechanism1-SHA1(0)}

RSASSA-PSS-params  ::=  SEQUENCE  {
	hashAlgorithm     [0] AlgorithmIdentifier DEFAULT
                                  sha1Identifier,
	maskGenAlgorithm  [1] AlgorithmIdentifier DEFAULT
                                  mgf1SHA1Identifier,
	saltLength        [2] INTEGER DEFAULT 20,
	trailerField      [3] INTEGER DEFAULT 1  
	}

sha1Identifier  AlgorithmIdentifier  ::=  {
	algorithm sha-1,
	parameters NULL  }
	
mgf1SHA1Identifier  AlgorithmIdentifier  ::=  {
	algorithm id-mgf1,
	parameters NULL }
	
	
-- rfc 3447

id-RSAES-OAEP OBJECT IDENTIFIER ::= { pkcs-1 7 }	

RSAES-OAEP-params ::= SEQUENCE {
	hashAlgorithm [0] HashAlgorithm DEFAULT hash-sha1,
	maskGenAlgorithm [1] MaskGenAlgorithm DEFAULT mgf1SHA1,
	pSourceAlgorithm [2] PSourceAlgorithm DEFAULT pSpecifiedEmpty
}

GCMParameters ::= SEQUENCE {
        aes-nonce        OCTET STRING, -- recommended size is 12 octets
        aes-ICVlen       AES-GCM-ICVlen DEFAULT 12 }

AES-GCM-ICVlen ::= INTEGER (12 | 13 | 14 | 15 | 16)


ALGORITHM-IDENTIFIER ::= CLASS {
    &id OBJECT IDENTIFIER UNIQUE,
    &Type OPTIONAL
}
    WITH SYNTAX { OID &id [PARAMETERS &Type] }

AlgorithmIdentifier { ALGORITHM-IDENTIFIER:InfoObjectSet } ::=
SEQUENCE {
    algorithm ALGORITHM-IDENTIFIER.&id({InfoObjectSet}),
    parameters
        ALGORITHM-IDENTIFIER.&Type({InfoObjectSet}{@.algorithm})
            OPTIONAL
}

HashAlgorithm ::= AlgorithmIdentifier {
	{OAEP-PSSDigestAlgorithms}
}
OAEP-PSSDigestAlgorithms ALGORITHM-IDENTIFIER ::= {
	{ OID sha1 PARAMETERS NULL }|
	{ OID id-sha256 PARAMETERS NULL }|
	{ OID id-sha384 PARAMETERS NULL }|
	{ OID id-sha512 PARAMETERS NULL },
	... -- Allows for future expansion --
}

hash-sha1 HashAlgorithm ::= {
	algorithm sha1,
	parameters SHA1Parameters : NULL
}
SHA1Parameters ::= NULL

MaskGenAlgorithm ::= AlgorithmIdentifier {
	{PKCS1MGFAlgorithms}
}
PKCS1MGFAlgorithms ALGORITHM-IDENTIFIER ::= {
	{ OID id-mgf1 PARAMETERS HashAlgorithm },
	... -- Allows for future expansion --
}

mgf1SHA1 MaskGenAlgorithm ::= {
	algorithm id-mgf1,
	parameters HashAlgorithm : sha1
}

PSourceAlgorithm ::= AlgorithmIdentifier {
	{PKCS1PSourceAlgorithms}
}
PKCS1PSourceAlgorithms ALGORITHM-IDENTIFIER ::= {
	{ OID id-pSpecified PARAMETERS EncodingParameters },
	... -- Allows for future expansion --
}
id-pSpecified OBJECT IDENTIFIER ::= { pkcs-1 9 }
EncodingParameters ::= OCTET STRING(SIZE(0..MAX))

pSpecifiedEmpty PSourceAlgorithm ::= {
	algorithm id-pSpecified,
	parameters EncodingParameters : emptyString
}
emptyString EncodingParameters ::= ''H



	
-- draft-ietf-pkix-ecc-pkalgs-02.txt'den alinanlar
	
ecdsa-with-Sha224 OBJECT IDENTIFIER ::= { id-ecSigType specified(3) 1 } 
ecdsa-with-Sha256 OBJECT IDENTIFIER ::= { id-ecSigType specified(3) 2 } 
ecdsa-with-Sha384 OBJECT IDENTIFIER ::= { id-ecSigType specified(3) 3 } 
ecdsa-with-Sha512 OBJECT IDENTIFIER ::= { id-ecSigType specified(3) 4 }

--RFC 3370 Cryptographic Message Syntax (CMS) Algorithms

--Content Encryption Algorithms
des-ede3-cbc OBJECT IDENTIFIER ::= { iso(1) member-body(2)
us(840) rsadsi(113549) encryptionAlgorithm(3) 7 }

rc2-cbc OBJECT IDENTIFIER ::= { iso(1) member-body(2) us(840)
rsadsi(113549) encryptionAlgorithm(3) 2 }

     --SEC 1: Elliptic Curve Cryptography Certicom Research
	 certicom-arc OBJECT IDENTIFIER ::= {iso(1) identified-organization(3) certicom(132)}
	 
	 --NIST Recommended EC Domain Parameters For PKIX
	 --<draft-ietf-pkix-ecc-nist-recommended-curves-00.txt>
     --OIDs for NIST Recommnded EC Domain Paramters
     secp192r1 OBJECT IDENTIFIER ::= { ansi-X9-62 curves(3) prime(1) 1 }
     sect163k1 OBJECT IDENTIFIER ::= { certicom-arc curve(0) 1 }
     sect163r2 OBJECT IDENTIFIER ::= { certicom-arc curve(0) 15 }
     secp224r1 OBJECT IDENTIFIER ::= { certicom-arc curve(0) 33 }
     sect233k1 OBJECT IDENTIFIER ::= { certicom-arc curve(0) 26 }
     sect233r1 OBJECT IDENTIFIER ::= { certicom-arc curve(0) 27 }
     secp256r1 OBJECT IDENTIFIER ::= { ansi-X9-62 curves(3) prime(1) 7 }
     sect283k1 OBJECT IDENTIFIER ::= { certicom-arc curve(0) 16 }
     sect283r1 OBJECT IDENTIFIER ::= { certicom-arc curve(0) 17 }
     secp384r1 OBJECT IDENTIFIER ::= { certicom-arc curve(0) 34 }
     sect409k1 OBJECT IDENTIFIER ::= { certicom-arc curve(0) 36 }
     sect409r1 OBJECT IDENTIFIER ::= { certicom-arc curve(0) 37 }
     secp521r1 OBJECT IDENTIFIER ::= { certicom-arc curve(0) 35 }
     sect571k1 OBJECT IDENTIFIER ::= { certicom-arc curve(0) 38 }
     sect571r1 OBJECT IDENTIFIER ::= { certicom-arc curve(0) 39 }


   secg-scheme OBJECT IDENTIFIER ::= { 
     iso(1) identified-organization(3) certicom(132) schemes(1) } 


   dhSinglePass-stdDH-sha224kdf-scheme OBJECT IDENTIFIER ::= { 
     secg-scheme 11 0 } 

   dhSinglePass-stdDH-sha256kdf-scheme OBJECT IDENTIFIER ::= { 
     secg-scheme 11 1 } 

   dhSinglePass-stdDH-sha384kdf-scheme OBJECT IDENTIFIER ::= { 
     secg-scheme 11 2 } 

   dhSinglePass-stdDH-sha512kdf-scheme OBJECT IDENTIFIER ::= { 
     secg-scheme 11 3 } 
	 


END
