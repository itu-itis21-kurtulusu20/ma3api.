EkdsElectronicIdentityCardApp

DEFINITIONS IMPLICIT TAGS ::= 

BEGIN

IMPORTS

	Certificate		              FROM Explicit
	CardHolderName	              FROM EkdsBaseDataDefs
	CardValidityDate              FROM EkdsBaseDataDefs
	DataObjectDigitalSignature    FROM EkdsCommonDataObjectDefs
	DataObjectVersionNumber       FROM EkdsCommonDataObjectDefs
	DataObjectErrorDetectionCode  FROM EkdsCommonDataObjectDefs;

--
--
-- APPLICATION (MF)
--
--

ElectronicIdentityCardApplication ::= SET
{
  cardHolderUID          CardHolderUniqueIdentifierDataObject,
  cardIssuerCert         CardIssuerCertificateDataObject,
  cardHolderFingerprint  FingerPrintDataObject,
  cardHolderVeinPrint    VeinPrintDataObject,
  cardHolderFacialImage  FacialImageDataObject,
  cardHolderIdentity			PersonalInformationDataObject,
  cardHolderDataAvailability	CardHolderDataAvailabilityDataObject
}

--
--
-- DATA OBJECTS (DF'S)
--
--

CardHolderUniqueIdentifierDataObject ::= [APPLICATION 1] SEQUENCE
{
  chuidData        [0] CHUIDData,
  digitalSignature [1] DataObjectDigitalSignature,
  errDetectionCode [2] DataObjectErrorDetectionCode
}

CHUIDData ::= SEQUENCE
{
  cardSerialNo     [0] CardSerialNumber,
  cardHolderID     [1] CardHolderIdentifier,
  cardHolderName   [2] CardHolderName,
  cardValidThru    [3] CardValidityDate
}

CardIssuerCertificateDataObject ::= [APPLICATION 2] Certificate  -- Bkz. ITU-T X.509

HandType ::= ENUMERATED 
{ 
	right (0), 
	left (1), 
    notInitialized(5)
}

FingerType ::= ENUMERATED
{
	 thumb		  (0), 
	 pointerFinger (1), 
	 middleFinger  (2), 
	 ringFinger    (3), 
	 littleFinger  (4),
	 notInitialized(5)
}


FingerPrintDataObject ::= [APPLICATION 3] SEQUENCE
{
  fingerPrintData       [0] FPData,
  dataObjectAttributes  [1] DataObjectAttributes,
  errDetectionCode      [2] DataObjectErrorDetectionCode
}

FPData ::=SEQUENCE
{
  cardDesc              [0] CardDescriptor,
  fingerPrintAlgoritmVersion             [1]  DataObjectVersionNumber,
  fingerPrintData1   [2] FingerPrintData,
  fingerPrintData2  [3] FingerPrintData
}


VeinPrintDataObject ::= [APPLICATION 4] SEQUENCE
{
  veinPrintData        [0] VPData,
  dataObjectAttributes [1] DataObjectAttributes,
  errDetectionCode     [2] DataObjectErrorDetectionCode
}

VPData ::= SEQUENCE
{
  cardDesc             [0] CardDescriptor,
  veinPrintAlgoritmVersion             [1]  DataObjectVersionNumber,
  veinPrintData1    [2] VeinPrintData,
  veinPrintData2   [3] VeinPrintData
}

FacialImageDataObject ::= [APPLICATION 5] SEQUENCE
{
  facialImageData      [0] FIData,
  dataObjectAttributes [1] DataObjectAttributes,
  errDetectionCode     [2] DataObjectErrorDetectionCode
}

FIData ::= SEQUENCE
{
  cardDesc             [0] CardDescriptor,
  imageData            [1] FacialImageData
}

PersonalInformationDataObject ::= [APPLICATION 6] SEQUENCE
{
  personelInfoData     [0] PIData,
  dataObjectAttributes [1] DataObjectAttributes,
  errDetectionCode     [2] DataObjectErrorDetectionCode
}

PIData ::= SEQUENCE
{
  cardDescriptor       [0] CardDescriptor,
  identityData         [1] IdentityData,
  registryData         [2] IdentityRegistryData
}

CardHolderDataAvailabilityDataObject ::= [APPLICATION 11] SEQUENCE
{
  fingerPrintAvailable  [0] BOOLEAN,
  veinPrintAvailable    [1] BOOLEAN,
  facialImageAvailable  [2] BOOLEAN,
  identityDataAvailable [3] BOOLEAN
}


--
--
-- SUB DATA DEFINITIONS
--
--

IdentityRegistryData ::= SEQUENCE
{
  bookletSerialNumber [0]  UTF8String    (SIZE(1..3)),	 -- Cüzdan seri no
  bookletNumber       [1]  UTF8String    (SIZE(1..6)),	 -- Cüzdan numarası
  registryNumber      [2]  NumericString (SIZE(1..7)),	 -- Kayıt numarası
  city                [3]  UTF8String    (SIZE(2..32)),	 -- Kayıtlı olduğu il
  cityCode            [4]  NumericString (SIZE(1..3)),	 -- Kayıtlı olduğu ilin (trafik) kodu
  cityWard            [5]  UTF8String    (SIZE(2..64)),	 -- Kayıtlı olduğu ilçe
  cityWardCode        [6]  NumericString (SIZE(1..6)),	 -- Kayıtlı olduğu ilçe kodu
  district            [7]  UTF8String    (SIZE(2..32)),	 -- Kayıtlı olduğu mahalle/köy (cilt tipi)
  volumeNumber        [8]  NumericString (SIZE(1..6)),	 -- Cilt numarası
  familyRowNumber     [9]  NumericString (SIZE(1..6)),	 -- Aile sıra numarası
  personRowNumber     [10] NumericString (SIZE(1..6)),	 -- Birey sıra numarası
  registeredIn        [11] UTF8String    (SIZE(2..32)),	 -- Verildiği yer
  registryReason      [12] UTF8String    (SIZE(2..24)),	 -- Veriliş nedeni
  registryDate        [13] GeneralizedTime				 -- Veriliş tarihi
}

IdentityData ::= SEQUENCE
{
  citizenNumber       [0] NumericString (SIZE(1..12)),   -- T.C. kimlik numarası
  citizenName			[1] UTF8String    (SIZE(2..64)), -- Adı
  citizenSurname		[2] UTF8String    (SIZE(2..64)), -- Soyadı   
  citizenFatherName		[3] UTF8String    (SIZE(0..64)), -- Baba adı  
  citizenFatherSurname	[4] UTF8String    (SIZE(0..64)), -- Baba soyadı  
  citizenMotherName		[5] UTF8String    (SIZE(0..64)), -- Ana adı  
  citizenMotherSurname	[6] UTF8String    (SIZE(0..64)), -- Ana soyadı  
  citizenBirthplace		[7] UTF8String    (SIZE(2..64)), -- Doğum yeri 
  citizenBirthDate		[8] BirthDateData,               -- Doğum tarihi  

  citizenSexuality	    [9] ENUMERATED {				 -- Cinsiyeti
  							male(0),
  							female(1),
							notInitialized(2)},

  citizenMaritalStatus  [10] ENUMERATED {			  	 -- Medeni hali
  							  single(0),                 -- Bekar
  							  married(1),                -- Evli
  							  widowed(2),                -- Dul
  							  divorced(3),               -- Boşanmış
							  cancelled(4),			     -- Evliliğin İptali
							  annulment(5),			     -- Evliliğin Feshi
							  notInitialized(6)},

  citizenStatus         [11] UTF8String (SIZE(0..24)),   -- Durumu
  citizenFormerSurname  [12] UTF8String (SIZE(0..64)),   -- Önceki soyadı
  citizenReligion       [13] UTF8String (SIZE(0..32)),   -- Dini
  citizenHandicap	    [14] INTEGER (0..100),           -- Özürlülük oranı

  citizenBloodGroup	    [15] ENUMERATED {				 -- Kan grubu
  								group_O(0),
  								group_A(1),
  								group_B(2),
  								group_AB(3),
								notInitialized(4)},

  citizenBloodRhesusFactor [16] ENUMERATED {			 -- Kan RH faktoru
  								positive(0),
  								negative(1),
								notInitialized(2)}
}

BirthDateData ::= SEQUENCE
{
	isValid           [0] BOOLEAN,
	validBirthDate    [1] GeneralizedTime,
	invalidBirthDate  [2] UTF8String
}

-- Sayısal parmakizi verisi için Bkz. ISO-1974, Part 4
-- Sayısal yüz resmi kodlaması için Bkz. JPEG 2000, ISO-19794, Part 5
-- Sayısal damarizi verisi için Bkz. ???

FingerPrintExcused ::= BOOLEAN

FingerPrintData ::= SEQUENCE
{
  fingerPrintExcused     [0] FingerPrintExcused, 
  hand [1] HandType,
  finger    [2] FingerType,
  imageData [1] OCTET STRING (SIZE(0..8192))
}

FacialImageData ::= OCTET STRING (SIZE(0..12288))

VeinPrintData ::= SEQUENCE
{
  veinPrintExcused  [0] FingerPrintExcused, 
  hand [1] HandType,
  finger    [2] FingerType,
  imageData [3] OCTET STRING (SIZE(0..512))
}



END
