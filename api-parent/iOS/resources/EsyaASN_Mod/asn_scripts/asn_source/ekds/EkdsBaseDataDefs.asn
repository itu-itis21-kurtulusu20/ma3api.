EkdsBaseDataDefs 

DEFINITIONS IMPLICIT TAGS ::=

BEGIN

--
-- EKDS Base Data Definitions
--

CardSerialNumber ::= UTF8String (SIZE(0..24))
CardHolderIdentifier ::= NumericString (SIZE(1..12))
ServiceProviderMark ::= OCTET STRING (SIZE(8))
CardValidityDate ::= GeneralizedTime
SecureAccessModuleSerialNumber ::= CardSerialNumber

ServiceRequestorRole ::= ENUMERATED
{
  roleClient      (0),
  roleParticipant (1)
}

ServiceProviderApplicationLabel ::= SEQUENCE
{
  label       [0] UTF8String,
  description [1] UTF8String
}

CardAccessDeviceSerialNumber ::= SEQUENCE
{
  deviceType     [0] CardAccessDeviceType,
  deviceUsage    [1] CardAccessDeviceUsage,
  deviceUniqueID [2] CardAccessDeviceUniqueIdentifier
}

CardAccessDeviceType ::= ENUMERATED
{
  personel       (0),
  institutional  (1),
  mobile         (2),
  emergency      (3),
  kiosk          (4),
  turnstile      (5),
  cardIssuance   (6)
}

CardAccessDeviceUsage ::= ENUMERATED
{
  developer      (0),
  integrator     (1),
  certification  (2),
  demonstration  (3),
  pilot          (4),
  operation      (5)
}

CardAccessDeviceUniqueIdentifier ::= OCTET STRING (SIZE(4))

CardHolderName ::= SEQUENCE
{
  cardHolderFirstName [0] UTF8String (SIZE(2..64)),
  cardHolderSurname   [1] UTF8String (SIZE(2..64))
}

IdentityVerificationAssurance ::= SEQUENCE
{
  applyForEachAuth [0] BOOLEAN,
  assuranceLevel   [1] ENUMERATED {
					     level_0 (0),
						 level_1 (1),
						 level_2 (2),
						 level_3 (3),
						 level_4 (4)
					   }
}

CardTemplateInfoDataObject ::= [PRIVATE 0] SEQUENCE
{
  cardType          [1] CardType,
  cardSerialNumber  [2] CardSerialNumber,
  templateName      [3] UTF8String (SIZE(0..16)),
  templateMajorVer  [4] UTF8String (SIZE(2)),
  templateMinorVer  [5] UTF8String (SIZE(2)),
  keyGroupNumber    [6] UTF8String (SIZE(2))
}

CardType ::= ENUMERATED 
{ 
  ekk (1), 
  gem (2), 
  sk  (3) 
}

BiometricVerificationStatus ::= ENUMERATED
{
  success            (0),
  failedButConfirmed (1),
  notApplicable      (2)
}

IdentityVerificationFailureResponse ::= ENUMERATED
{
  sendMessage  (0),
  revocateCard (1)
}

IdentityVerificationConstraint ::= ENUMERATED
{
  singleCard       (0),
  dependentOnOther (1)
}

CodedData ::= SET
{
  codeSchemeIdentifier [0] ENUMERATED { none(0), icd10(1), ...},
  codeLength           [1] INTEGER,
  codeDataValue        [2] OCTET STRING,
  codeDataFreeText     [3] UTF8String (SIZE(0..80)) OPTIONAL
}

CardDescriptor ::= SEQUENCE
{
  cardSerialNo [0] CardSerialNumber,
  cardHolderID [1] CardHolderIdentifier
}

TimeStamp ::= SEQUENCE 
{
  time     [0] UTCTime,
  signData [1] DataObjectDigitalSignature
}



END
