pkcs1pkcs8

DEFINITIONS IMPLICIT TAGS ::=
BEGIN

-- EXPORTS All --
	-- All types and values defined in this module are exported for use
	-- in other ASN.1 modules.

IMPORTS
	
	
	AlgorithmIdentifier,Version
	FROM Explicit { iso(1) identified-organization(3) dod(6) internet(1)
  security(5) mechanisms(5) pkix(7) id-mod(0) id-pkix1-explicit(18) }
	--Attributes
	--FROM pkcs10
;

PrivateKeyInfo ::= SEQUENCE {
	version Version,
	privateKeyAlgorithm AlgorithmIdentifier,
	privateKey PrivateKey,
	attributes [0] IMPLICIT Attributes OPTIONAL 
	}


PrivateKey ::= OCTET STRING


EncryptedPrivateKeyInfo ::= SEQUENCE {
	encryptionAlgorithm AlgorithmIdentifier,
	encryptedData EncryptedData }

EncryptedData ::= OCTET STRING

--PKCS1 basliyor

RSAPublicKey ::= SEQUENCE {
	modulus INTEGER, -- n
	publicExponent INTEGER -- e 
	}
	
RSAPrivateKey ::= SEQUENCE {
	version Version,
	modulus INTEGER, -- n
	publicExponent INTEGER, -- e
	privateExponent INTEGER, -- d
	prime1 INTEGER, -- p
	prime2 INTEGER, -- q
	exponent1 INTEGER, -- d mod (p-1)
	exponent2 INTEGER, -- d mod (q-1)
	coefficient INTEGER -- (inverse of q) mod p 
	}
	
END
