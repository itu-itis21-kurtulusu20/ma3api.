dercms { iso(1) member-body(2) us(840) rsadsi(113549)
      pkcs(1) pkcs-9(9) smime(16) modules(0) cms-2004(24) }

   DEFINITIONS IMPLICIT TAGS ::=
   BEGIN

   -- EXPORTS All
   -- The types and values defined in this module are exported for use
   -- in the other ASN.1 modules.  Other applications may use them for
   -- their own purposes.

   IMPORTS

     -- Imports from RFC 3280 [PROFILE], Appendix A.1
           Attribute, AlgorithmIdentifier
              FROM Explicit
                   { iso(1) identified-organization(3) dod(6)
                     internet(1) security(5) mechanisms(5) pkix(7)
                     mod(0) pkix1-explicit(18) }


	  
;
   -- DER Cryptographic Message Syntax

   AuthAttributes ::= SET SIZE (1..MAX) OF Attribute
   SignedAttributes ::= SET SIZE (1..MAX) OF Attribute
   SignatureValue ::= OCTET STRING



-- ECC CMS yapisi. 04.09.2009 da eklendi

     ECC_CMS_SharedInfo  ::=  SEQUENCE { 
       keyInfo         AlgorithmIdentifier, 
       entityUInfo [0] EXPLICIT OCTET STRING OPTIONAL, 
       suppPubInfo [2] EXPLICIT OCTET STRING  } 




   END -- of DER CryptographicMessageSyntax2004
